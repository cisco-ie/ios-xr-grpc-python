module debug_trace {
  namespace "http://cisco.com/calvados/debug_trace";
  prefix debug_trace;
  organization "Cisco Systems, Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.
This module contains definitions
for the following management objects:
debug_trace: Calvados debug trace.

Copyright (c) 2015-2016 by Cisco Systems, Inc.
All rights reserved.

    Copyright (c) 2012-2016 by Cisco Systems, Inc.
     All rights reserved.";
  revision 2015-12-03 {
    description
      "Initial version.";
  }

  uses config-debug-trace-group;

  grouping config-debug-trace-group {
    container config {
      config true;
      container debug {
        list trace {
          max-elements "16";
          key "connection_type";
          leaf connection_type {
            type string;
          }
          choice trace-output {
            leaf enable {
              type empty;
            }
            leaf disable {
              type empty;
            }
          }
        }
      }
    }
  }
}
