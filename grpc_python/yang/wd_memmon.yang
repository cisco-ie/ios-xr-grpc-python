module wd_memmon {
  namespace "http://cisco.com/calvados/wd_memmon";
  prefix wd_memmon;

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2016 by Cisco Systems, Inc.
     All rights reserved.";

  revision "2015-08-30" {
    description "Initial version.";
  }


  typedef percent {
    type int32 {
      range "0 .. 100";
    }
    description
      "Percentage";
  }
  container memory_status_config {
    leaf minor {
      type percent;
      default "80";
      description
        "Memory  Monitoring Minor Threshold";
    }
    leaf severe {
      type percent;
      default "90";
      description
        "Memory Monitoring Severe Threshold";
    }
    leaf critical {
      type percent;
      default "95";
      description
        "Memory Monitoring Critial Threshold";
    }
    leaf recovery_enabled {
      type boolean;
      default "false";
      description
        "In case of Critical Memory Usage, Recovery Action Enabled/Disabled";
    }
    must " (critical > severe and severe > minor)" {
      error-message " ERROR: Threshold values are not matching condition: minor < severe < critical";
    }
  }
  container memory_status {
    description
      "Memory Info";
    config false;
    list all-locations {
      key "location";
      leaf location {
        type string;
      }
      list all-device {
        key "device";
        leaf device {
          type string;
        }
        leaf minor {
          type string;
          description
            "Mem  Monitoring Minor Threshold";
        }
        leaf severe {
          type string;
          description
            "Mem  Monitoring severe Threshold";
        }
        leaf critical {
          type string;
          description
            "Mem  Monitoring Critical Threshold";
        }
        leaf current_state {
          type string;
          description
            " Current state of Physical Memory ";
        }
        leaf total_used {
          type string;
          description
            " Total Used Memory ";
        }
        leaf available {
          type string;
          description
            " Total Available Physical Memory ";
        }
      }
    }
  }
}
