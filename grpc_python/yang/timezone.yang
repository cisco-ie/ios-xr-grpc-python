module timezone {
  namespace "http://cisco.com/calvados/timezone";
  prefix timezone;
  import show_trace {
    prefix show_trace;
  }
  organization "Cisco Systems, Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG definitions
for Cisco IOS-XR syadmin TOD configuration and cli.

This module contains definitions
for the following management objects:
Time of the Day(TOD) Cli and configuration data

Copyright (c) 2013-2016 by Cisco Systems, Inc.
All rights reserved.

    Copyright (c) 2012-2016 by Cisco Systems, Inc.
     All rights reserved.";
  revision 2016-07-04 {
    description
      "Remove refine stmt";
  }

  container clock {
    container timezone {
      leaf tzname {
        type string;
      }
      leaf area {
        type string;
      }
    }
    container trace {
      config false;
      container timezone_config {
        uses show_trace:traceable;
      }
      container timezone_notify {
        uses show_trace:traceable;
      }
    }
  }
}
