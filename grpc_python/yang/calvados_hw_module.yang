module calvados_hw_module {
  namespace "http://cisco.com/panini/calvados/calvados_hw_module";
  prefix calvados_hw_module;
  import sm_hw_mod {
    prefix shelf_mgr;
  }
  import led_mgr_ui {
    prefix led_mgr;
  }
  import shhwfpd {
    prefix shhwfpd;
  }
  import obflconf {
    prefix obflconf;
  }
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

This module defines the top level container for
all 'hw-module' commands for Sysadmin.

Copyright(c) 2012-2016 by Cisco Systems, Inc.
All rights reserved.

    Copyright (c) 2012-2016 by Cisco Systems, Inc.
     All rights reserved.";
  revision 2012-07-03 {
    description
      "Created initial 'hw-module' refactorization";
  }

  container hw-module {
    container config {
      config true;
      uses shelf_mgr:hw-module-config-group;
      uses led_mgr:hw-module-config-group;
      uses obflconf:hw-module-config-group;
    }
    container oper {
      config false;
      list location {
        key "location";
        leaf location {
          type string;
        }
        container actions {
          uses shelf_mgr:hw-module-action-group;
        }
        container show {
        }
      }
    }
    uses shhwfpd:hw-module-oper-group;
  }
}
