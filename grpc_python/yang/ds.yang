module ds {
  namespace "http://cisco.com/panini/calvados/ds";
  prefix ds;
  import ietf-inet-types {
    prefix inet;
  }
  import show_trace {
    prefix show_trace;
  }
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

The Directory Services (DS).

Copyright(c) 2010-2016 by Cisco Systems, Inc.
All rights reserved.

    Copyright (c) 2012-2016 by Cisco Systems, Inc.
     All rights reserved.";
  revision 2016-10-12 {
    description
      "Unhide commands and configs. Moved to advanced-grp";
  }


  typedef service-scope {
    type enumeration {
      enum "None" {
      }
      enum "Rack" {
      }
      enum "System" {
      }
      enum "Node" {
      }
    }
  }

  typedef process-role {
    type enumeration {
      enum "NoRole" {
      }
      enum "Active" {
      }
      enum "Standby" {
      }
      enum "None" {
      }
      enum "Unknown" {
        value 254;
      }
    }
  }

  typedef process-issu-role {
    type enumeration {
      enum "Primary" {
        value 1;
      }
      enum "Secondary" {
        value 2;
      }
      enum "Tertiary" {
        value 3;
      }
      enum "Unknown" {
        value 254;
      }
    }
  }

  grouping servicesGroup {
    list services {
      key "name";
      leaf name {
        type string;
        description
          "Name of the service";
      }
      list endpoint {
        description
          "endpoint info for a service in DS";
        leaf scope {
          type service-scope;
        }
        leaf ip {
          type inet:ipv4-address;
        }
        leaf port {
          type inet:port-number;
        }
        leaf role {
          type process-role;
        }
        leaf issu_role {
          type process-issu-role;
        }
        leaf node {
          type string;
          description
            "Ethernet address of the node hosting the endpoint";
        }
      }
      list registrations {
        description
          "clients registered for a service in DS";
        leaf client {
          type string;
        }
        leaf pid {
          type uint32;
        }
      }
    }
  }
  container services {
    description
      "Directory Services Entries";
    config false;
    list all-locations {
      key "location";
      leaf location {
        type string;
        description
          "Node Location";
      }
      uses servicesGroup;
    }
  }
  container services-stats {
    description
      "Directory Services Stats";
    config false;
    container ds {
      config false;
      uses show_trace:traceable;
    }
    list all-locations {
      key "location";
      leaf location {
        type string;
      }
      list stats {
        key "name";
        leaf name {
          type string;
          description
            "Name of the service";
        }
        leaf published {
          type uint32;
          description
            "number of endpoints published for this service";
        }
        leaf deleted {
          type uint32;
          description
            "number of endpoints deleted for this service";
        }
        leaf modified {
          type uint32;
          description
            "number of endpoints modified for this service";
        }
        leaf registered {
          type uint32;
          description
            "number of clients registered for this service";
        }
        leaf unregistered {
          type uint32;
          description
            "number of clients un-registered for this service";
        }
        leaf notifications {
          type uint32;
          description
            "number of clients notified for this service";
        }
        leaf remote_sent {
          type uint32;
          description
            "number of remote service updates sent to remote nodes";
        }
        leaf remote_recv {
          type uint32;
          description
            "number of remote service received from remote nodes";
        }
      }
    }
  }
}
