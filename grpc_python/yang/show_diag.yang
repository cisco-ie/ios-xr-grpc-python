module show_diag {
  namespace "http://www.cisco.com/calvados/show_diag";
  prefix show_diag;
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

This module holds diag data for chassis, card, fan, power.

Copyright(c) 2012-2016 by Cisco Systems, Inc.
All rights reserved.

    Copyright (c) 2012-2016 by Cisco Systems, Inc.
     All rights reserved.";
  revision 2012-03-27 {
    description
      "Initial revision of show diag commands";
  }


  grouping diag-default-data {
    container default {
      list default_list {
        key "location";
        leaf location {
          type string;
        }
        container default-data {
          leaf-list default_out_list {
            type string;
          }
        }
      }
    }
    container fans {
      list fans_list {
        key "location";
        leaf location {
          type string;
        }
        container default-data {
          leaf-list default_out_list {
            type string;
          }
        }
      }
    }
    container power-supply {
      list pwr_list {
        key "location";
        leaf location {
          type string;
        }
        container default-data {
          leaf-list default_out_list {
            type string;
          }
        }
      }
    }

    grouping chassis_eeprom_grp {
      container chassis_eeprom_cnt {
        list chassis_eeprom_list {
          key "location";
          leaf location {
            type string;
          }
          container eeprom-data {
            leaf-list raw_list {
              type string;
            }
          }
        }
      }
    }

    grouping chassis_grp {
      container chassis_cnt {
        list chassis_list {
          key "location";
          leaf location {
            type string;
          }
          container default-data {
            leaf-list default_out_list {
              type string;
            }
          }
        }
      }
    }
    container chassis {
      uses chassis_grp;
      uses chassis_eeprom_grp;
    }
  }

  grouping diag-summary-data {
    container summary {
      list summary_list {
        key "location";
        leaf location {
          type string;
        }
        container summary-data {
          leaf-list summary_out_list {
            type string;
          }
        }
      }
    }
  }

  grouping diag-detail-data {
    container detail {
      list detail_list {
        key "location";
        leaf location {
          type string;
        }
        container detail-data {
          leaf-list detail_out_list {
            type string;
          }
        }
      }
    }
  }

  grouping diag-eeprom-location-data {
    container eeprom {
      list eeprom_list {
        key "location";
        leaf location {
          type string;
        }
        container eeprom-data {
          leaf-list raw_list {
            type string;
          }
        }
      }
    }
  }
  container diag {
    config false;
    description
      "diag data";
    uses diag-default-data;
    uses diag-summary-data;
    uses diag-eeprom-location-data;
    uses diag-detail-data;
  }
}
