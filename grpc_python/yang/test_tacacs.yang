module test_tacacs {
  namespace "http://www.cisco.com/calvados/test_tacacs";
  prefix test_tacacs;
  import tacacs_server {
    prefix tacacs-server;
  }
  organization "Cisco Systems Inc.";
  contact
    "aaa-ng-tacacs-dev@cisco.com";

  description 
    "This module contains definitions
     for the Calvados model objects.

    This clie part is for test commands for tacacs

    Copyright (c) 2012-2016 by Cisco Systems, Inc.
     All rights reserved.";
  revision 2015-07-07 {
    description
      "Initial revision";
  }

  augment "/tacacs-server:tacacs-server" {
    container test-authentication {
      presence "";
      config false;
      leaf authentication {
        type string;
        mandatory false;
        description
          "Authentication";
      }
    }
    container test-authorization {
      presence "";
      config false;
      leaf authorization {
        type string;
        mandatory false;
        description
          "Authorization";
      }
    }
    container test-accounting {
      presence "";
      config false;
      leaf accounting {
        type string;
        mandatory false;
        description
          "Accounting";
      }
    }
  }
}
