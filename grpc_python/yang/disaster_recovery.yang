module disaster_recovery {
  namespace "http://www.cisco.com/ns/calvados/confd_helper/disaster-recovery";
  prefix disaster-recovery;
  import tailf-common {
    prefix tailf;
  }
  import tailf-aaa {
    prefix aaa;
  }
  organization "Cisco Systems Inc.";
  contact
    "clos-mgbl@cisco.com";

  description 
    "This module contains definitions
     for the Calvados model objects.

    This module defines the system users authentication 
credentials and virtual IP that can be modified in 
runtime.

    Copyright (c) 2012-2016 by Cisco Systems, Inc.
     All rights reserved.";
  revision 2011-06-20 {
    description
      "Initial revision";
  }

  augment "/aaa:aaa" {
    container disaster-recovery {
      leaf username {
        type leafref {
          path "/aaa:aaa/aaa:authentication/aaa:users/aaa:user/aaa:name";
        }
      }
      leaf password {
        type tailf:md5-digest-string;
      }
    }
  }
}
