module SNMP-COMMUNITY-MIB {
  namespace "http://tail-f.com/ns/mibs/SNMP-COMMUNITY-MIB/200308060000Z";
  prefix SNMP_COMMUNITY_MIB;
  import tailf-common {
    prefix tailf;
  }
  import SNMPv2-TC {
    prefix SNMPv2_TC;
  }
  import SNMP-TARGET-MIB {
    prefix SNMP_TARGET_MIB;
  }
  import SNMP-FRAMEWORK-MIB {
    prefix SNMP_FRAMEWORK_MIB;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2016 by Cisco Systems, Inc.
     All rights reserved.";
  revision 2003-08-06 {
    description
      "";
  }

  container SNMP-COMMUNITY-MIB {
    container snmpCommunityTable {
      list snmpCommunityEntry {
        key "snmpCommunityIndex";
        leaf snmpCommunityIndex {
          type snmpCommunityIndexType;
        }
        leaf snmpCommunityName {
          type snmpCommunityNameType;
          mandatory true;
        }
        leaf snmpCommunitySecurityName {
          type snmpCommunitySecurityNameType;
          mandatory true;
        }
        leaf snmpCommunityContextEngineID {
          type SNMP_FRAMEWORK_MIB:SnmpEngineID;
          mandatory true;
        }
        leaf snmpCommunityContextName {
          type snmpCommunityContextNameType;
          default "";
        }
        leaf snmpCommunityTransportTag {
          type SNMP_TARGET_MIB:SnmpTagValue;
          default "";
        }
        leaf snmpCommunityStorageType {
          type SNMPv2_TC:StorageType;
          default "permanent";
        }
      }
    }
  }

  typedef snmpCommunityIndexType {
    type string {
      length "1 .. 32";
    }
  }

  typedef snmpCommunityNameType {
    type string;
  }

  typedef snmpCommunitySecurityNameType {
    type string {
      length "1 .. 32";
    }
  }

  typedef snmpCommunityContextNameType {
    type string {
      length "min .. 32";
    }
  }

  typedef snmpTargetAddrNameType {
    type string {
      length "1 .. 32";
    }
  }

  typedef snmpTargetAddrTMaskType {
    type tailf:hex-list {
      pattern "(((([0-9A-Fa-f]{2}):){0,254}([0-9A-Fa-f]{2}))){0,1}";
    }
  }

  typedef snmpTargetAddrMMSType {
    type int32 {
      range "0 .. 2147483647";
    }
  }
}
