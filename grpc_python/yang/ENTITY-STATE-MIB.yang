/*
 * Generated by confdc --mib2yang
 * Source: ENTITY-STATE-MIB.mib
 * 
 * Copyright (c) 2015-2016 by Cisco Systems, Inc.
 * All rights reserved.
 */
module ENTITY-STATE-MIB {
  namespace "http://tail-f.com/ns/mibs/ENTITY-STATE-MIB/200511220000Z";
  prefix ENTITY_STATE_MIB;
  tailf:id "";
  tailf:snmp-mib-module-name "ENTITY-STATE-MIB";

  import ietf-yang-types {
    prefix yang;
  }
  import tailf-common {
    prefix tailf;
  }
  import ENTITY-STATE-TC-MIB {
    prefix ENTITY-STATE-TC-MIB;
  }
  import ENTITY-MIB {
    prefix ENTITY-MIB;
  }

  organization    "Cisco Systems Inc.";

  contact         "Cisco Systems, Inc.
                   Customer Service

                   Postal: 170 West Tasman Drive
                   San Jose, CA 95134

                   Tel: +1 800 553-NETS

                   E-mail: cs-yang@cisco.com";

  description     "This module contains a collection of YANG
                   definitions for Cisco IOS-XR SysAdmin configuration.

                   Copyright(c) 2015-2016 by Cisco Systems, Inc.
                   All rights reserved.";

  revision 2005-11-22 {
    description
      "";
  }

  container ENTITY-STATE-MIB {
    container entStateTable {
      config false;
      tailf:callpoint cp_snmp_entStateTable;
      list entStateEntry {
        key "entPhysicalIndex";
        tailf:sort-order "snmp";
        config false;
        tailf:snmp-oid "1.3.6.1.2.1.131.1.1";
        leaf entPhysicalIndex {
          type ENTITY-MIB:PhysicalIndex;
          tailf:snmp-oid "1.3.6.1.2.1.47.1.1.1.1.1";
        }
        leaf entStateLastChanged {
          type yang:date-and-time;
          tailf:snmp-oid "1.3.6.1.2.1.131.1.1.1.1";
          config false;
        }
        leaf entStateAdmin {
          type ENTITY-STATE-TC-MIB:EntityAdminState;
          tailf:snmp-oid "1.3.6.1.2.1.131.1.1.1.2";
          config false;
        }
        leaf entStateOper {
          type ENTITY-STATE-TC-MIB:EntityOperState;
          tailf:snmp-oid "1.3.6.1.2.1.131.1.1.1.3";
          config false;
        }
        leaf entStateUsage {
          type ENTITY-STATE-TC-MIB:EntityUsageState;
          tailf:snmp-oid "1.3.6.1.2.1.131.1.1.1.4";
          config false;
        }
        leaf entStateAlarm {
          type ENTITY-STATE-TC-MIB:EntityAlarmStatus;
          tailf:snmp-oid "1.3.6.1.2.1.131.1.1.1.5";
          config false;
        }
        leaf entStateStandby {
          type ENTITY-STATE-TC-MIB:EntityStandbyStatus;
          tailf:snmp-oid "1.3.6.1.2.1.131.1.1.1.6";
          config false;
        }
      }
    }
  }
}
