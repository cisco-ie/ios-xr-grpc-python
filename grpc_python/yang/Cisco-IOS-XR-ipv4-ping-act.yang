submodule Cisco-IOS-XR-ipv4-ping-act {

    belongs-to Cisco-IOS-XR-ping-act {
        prefix "ping-act";
    }

    import Cisco-IOS-XR-types { prefix "xr"; }

    organization "Cisco Systems, Inc.";
    
    contact
    "Cisco Systems, Inc.
     Customer Service

     Postal: 170 West Tasman Drive
     San Jose, CA 95134

     Tel: +1 800 553-NETS

     E-mail: cs-yang@cisco.com";

    description 
    "This module contains a collection of YANG definitions
     for Cisco IOS-XR IPv4 ping action package configuration.

     Copyright (c) 2016 by Cisco Systems, Inc.
     All rights reserved.";
    
    revision "2016-08-20" {
        description
            "IOS XR 6.2.1 revision.";
    }

    grouping PING-COMMON-INPUT-OUTPUT-OPTIONS {

       leaf destination {
           description "Ping destination address or hostname";
           type string; 
           mandatory true;
       }

       leaf repeat-count {
           description "Number of ping packets to be sent out";
           type uint64 {
               range "1..2147483647";
           }
           default 5;
       }

       leaf data-size {
           description "Size of ping packet";
           type uint64 {
               range "36..18024";
           }
           default 100;
       }

       leaf timeout {
           description "Timeout in seconds";
           type uint64 {
               range "0..3600";
           }
           default 2;
       }

       leaf interval {
           description "Ping interval in milli seconds";
           type uint32 {
               range "0..3600000";
           }
           default 10;
       }    

       leaf pattern {
           description "Pattern of payload data";
           type xr:Hex-integer; 
       }

       leaf sweep {
           description "Sweep is enabled";
           type boolean;
       }
   }

   grouping PING-OPTIONS { 

       uses PING-COMMON-INPUT-OUTPUT-OPTIONS;
       
       leaf vrf-name {
           description "VRF name";
           type string;
       }

       leaf source {
           description "Source address or interface";
           type string;
       }

       leaf verbose {
           description "Validate return packet";
           type boolean;
       }

   }

   grouping IPV4-SPECIFIC-OPTIONS {

       leaf type-of-service {
           description "Type of Service";
           type uint8 {
               range "0..255";
           }
       }

       leaf do-not-frag {
           description "Do Not Fragment";
           type boolean;
       }

       leaf validate {
           description "Validate return packet";
           type boolean;
       }
   }

   grouping IPV4-PING-OPTIONS {
    
       uses PING-OPTIONS; 
       
       uses IPV4-SPECIFIC-OPTIONS;
      
   }

   grouping IPV4-PING-INPUT {

           uses IPV4-PING-OPTIONS;
   }

   grouping IPV4-PING-OUTPUT { 

       uses PING-COMMON-INPUT-OUTPUT-OPTIONS;

       list reply-list {
           key result;

           leaf result {
               description "Response for each packet";
               type string;
           } 

           list reply-address-list {
               key reply-address;

               leaf reply-address {
                   description "Broadcast reply address";
                   type string;
               }

               leaf result {
                   description "Sign for each reply packet";
                   type string;
               } 

           } 
       }    

       leaf hits {
           description "Number of packets reach to destination and get reply back";
           type uint64;
       }

       leaf total {
           description "Total number of packets sent out";
           type uint64;
       }

       leaf success-rate {
           description "Successful rate of ping";
           type uint64;
       }

       leaf rtt-min {
           description "Minimum value of Round Trip Time";
           type uint64;
       }

       leaf rtt-avg {
           description "Average value of Round Trip Time";
           type uint64;
       }

       leaf rtt-max {
           description "Maximum value of Round Trip Time";
           type uint64;
       }

       leaf sweep-min {
           description "Minimum value of sweep size";
           type uint32;
       }

       leaf sweep-max {
           description "Maximum value of sweep size";
           type uint64;
       }

       leaf rotate-pattern {
           description "Rotate Pattern is enabled";
           type boolean;
       }

       leaf ping-error-response {
           description "Error response for each ping, in case of bulk ping";
           type string;
       }
   }
}
