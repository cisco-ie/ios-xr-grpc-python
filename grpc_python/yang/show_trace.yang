module show_trace {
  namespace "http://cisco.com/calvados/show_trace";
  prefix show_trace;
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

Copyright(c) 2012-2016 by Cisco Systems, Inc.
All rights reserved.

    Copyright (c) 2012-2016 by Cisco Systems, Inc.
     All rights reserved.";
  revision 2016-05-11 {
    description
      "Initial version.";
  }


  grouping traceable {
    list trace {
      description
        "show traceable processes";
      config false;
      key "buffer";
      leaf buffer {
        type string;
      }
      list location {
        key "location_name";
        leaf location_name {
          type string;
        }
        list all-options {
          key "option";
          leaf option {
            type string;
          }
          list trace-blocks {
            leaf data {
              type string;
              description
                "Trace output block";
            }
          }
        }
      }
    }
  }

  grouping traceable_process {
    list instance {
      description
        "show traceable process instance names";
      config false;
      key "process_name";
      leaf process_name {
        type string;
      }
      list trace {
        description
          "show traceable processes";
        config false;
        key "buffer";
        leaf buffer {
          type string;
        }
        list location {
          key "location_name";
          leaf location_name {
            type string;
          }
          list all-options {
            key "option";
            leaf option {
              type string;
            }
            list trace-blocks {
              leaf data {
                type string;
                description
                  "Trace output block";
              }
            }
          }
        }
      }
    }
  }

  grouping traceable_with_keypath_location {
    list trace {
      config false;
      key "buffer";
      leaf buffer {
        type string;
      }
      list all-options {
        key "option";
        leaf option {
          type string;
        }
        list trace-blocks {
          leaf data {
            type string;
          }
        }
      }
    }
  }
}
