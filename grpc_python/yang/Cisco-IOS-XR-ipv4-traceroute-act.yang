submodule Cisco-IOS-XR-ipv4-traceroute-act {

    belongs-to Cisco-IOS-XR-traceroute-act {
        prefix "traceroute-act";
    }

    organization "Cisco Systems, Inc.";
    
    contact
    "Cisco Systems, Inc.
     Customer Service

     Postal: 170 West Tasman Drive
     San Jose, CA 95134

     Tel: +1 800 553-NETS

     E-mail: cs-yang@cisco.com";

    description 
    "This module contains a collection of YANG definitions
     for Cisco IOS-XR IPv4 traceroute action package configuration.

     Copyright (c) 2016 by Cisco Systems, Inc.
     All rights reserved.";
    
    revision "2016-09-17" {
        description
            "IOS XR 6.2.1 revision.";
    }

    grouping TRACEROUTE-OPTIONS {

        leaf destination {
            description "Destination address or hostname";
            type string;
            mandatory true;
        }

        leaf source {
            description "Source address or interface";
            type string;
        }

        leaf timeout {
            description "Timeout in seconds";
            type uint32 {
                range "0..3600";
            }
            default 3;
        }

        leaf probe {
            description "Probe count";
            type uint16 {
                range "1..65535";
            }
            default 3;
        }

        leaf numeric {
            description "Numeric display only";
            type boolean;
        }

        leaf vrf-name {
            description "VRF name";
            type string;
        }

        leaf min-ttl {
            description "minimum time to live";
            type uint16 {
                range "0..255";
            }
            default 1;
        }

        leaf max-ttl {
            description "maximum time to live";
            type uint16 {
                range "0..255";
            }
            default 30;
        }

        leaf port {
            description "Port numbe";
            type uint32 {
                range "0..65535";
            }
        }

        leaf verbose {
            description "verbose output";
            type boolean;
        }
    }

    grouping TRACEROUTE-OUTPUT {

        leaf destination {
            description "Destination address or hostname";
            type string;
        }
             
        list hops {
            key hop-index;

            leaf hop-index {
                description "Index of the hop";
                type uint32;
            }

            leaf hop-address {
                description "Address of the hop";
                type string;
            }

            leaf hop-hostname {
                description "Hostname of the hop";
                type string;
            }

            list probes {
                key probe-index;

                leaf probe-index {
                    description "Index of the probe";
                    type uint32;
                }

                leaf result {
                    description "Response for each probe";
                    type string;
                } 

                leaf delta-time {
                    description "Delta time in seconds";
                    type uint32;
                }

                leaf hop-address {
                    description "Address of the hop";
                    type string;
                }

                leaf hop-hostname {
                    description "Hostname of the hop";
                    type string;
                }
            }    
        }

        leaf verbose-output {
            description "Verbose output";
            type string;
        }
    }
}
