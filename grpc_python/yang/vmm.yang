module vmm {
  namespace "http://cisco.com/calvados/vmm";
  prefix vmmh;
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

Copyright(c) 2012-2016 by Cisco Systems, Inc.
All rights reserved.

    Copyright (c) 2012-2016 by Cisco Systems, Inc.
     All rights reserved.";
  revision 2016-05-12 {
    description
      "Initial Version";
  }

  container VM {
    description
      "VM Info";
    config false;
    list all-locations {
      key "location";
      leaf location {
        type string;
      }
      list all-uiids {
        key "uiid";
        leaf uiid {
          type string;
          description
            "Unique Immutable ID";
        }
        leaf id {
          type string;
          description
            "ID of the VM";
        }
        leaf status {
          type string;
          description
            "Status of the VM";
        }
        leaf ipaddr {
          type string;
          description
            "CE IP address";
        }
        leaf hb_interval_s {
          type string;
          description
            "Heartbeat interval sec";
        }
        leaf hb_interval_ns {
          type string;
          description
            "Heartbeat interval nsec";
        }
        leaf last_hb_sent {
          type string;
          description
            "Last heartbeat sent";
        }
        leaf last_hb_rec {
          type string;
          description
            "Last heartbeat received";
        }
        leaf role {
          type string;
          description
            "ISSU role";
        }
      }
    }
  }
}
