module Cisco-IOS-XR-man-http-lighttpd-yang-cfg {

  /*** NAMESPACE / PREFIX DEFINITION ***/

  namespace "http://cisco.com/ns/yang"+
    "/Cisco-IOS-XR-man-http-lighttpd-yang-cfg";


  prefix "man-http-lighttpd-yang-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-http-lighttpd-yang package configuration.

     This module contains definitions
     for the following management objects:
       web: Webserver configuration commands

     Copyright (c) 2013-2016 by Cisco Systems, Inc.
     All rights reserved.";

  revision "2015-11-09" {
    description
      "IOS XR 6.0 revision.";
  }


  container web {
    description "Webserver configuration commands";

    container server {
      description "Webserver configuration commands";

      container service {
        description "Web Service that needs to be activated";

        container restconf {
          presence "Indicates a restconf node is configured.";
          description "Restconf specific configurations";
          leaf http-port {
            type int32;
            description "Port number http server is listening on";
          }
          leaf http-enable {
            type empty;
            description
              "Enable http connection in addition to https";
          }
          leaf https-port {
            type int32;
            description "Port number https server is listening on";
          }
          leaf enable {
            type empty;
            mandatory true;
            description "Enable RESTCONF Service";
          }
        }
      }
    }
  }
}
