/*
 * Generated by confdc --mib2yang
 * Source: ENTITY-MIB.mib
 *
 * Copyright (c) 2015-2016 by Cisco Systems, Inc.
 * All rights reserved.
 */
module ENTITY-MIB {
  namespace "http://tail-f.com/ns/mibs/ENTITY-MIB/199912070000Z";
  prefix ENTITY_MIB;
  tailf:id "";
  tailf:snmp-mib-module-name "ENTITY-MIB";

  import ietf-yang-types {
    prefix yang;
  }
  import tailf-common {
    prefix tailf;
  }
  import SNMPv2-TC {
    prefix SNMPv2-TC;
  }
  import SNMP-FRAMEWORK-MIB {
    prefix SNMP-FRAMEWORK-MIB;
  }

  organization    "Cisco Systems Inc.";

  contact         "Cisco Systems, Inc.
                   Customer Service

                   Postal: 170 West Tasman Drive
                   San Jose, CA 95134

                   Tel: +1 800 553-NETS

                   E-mail: cs-yang@cisco.com";

  description     "This module contains a collection of YANG
                   definitions for Cisco IOS-XR SysAdmin configuration.

                   Copyright(c) 2015-2016 by Cisco Systems, Inc.
                   All rights reserved.";

  revision 1999-12-07 {
    description
      "";
  }

  container ENTITY-MIB {
    container entityGeneral {
      tailf:snmp-oid "1.3.6.1.2.1.47.1.4";
      config false;
      leaf entLastChangeTime {
        type yang:timestamp;
        tailf:snmp-oid "1.3.6.1.2.1.47.1.4.1";
        config false;
      }
    }
    container entPhysicalTable {
      config false;
      tailf:callpoint cp_snmp_entPhysicalTable;
      list entPhysicalEntry {
        key "entPhysicalIndex";
        tailf:sort-order "snmp";
        config false;
        tailf:snmp-oid "1.3.6.1.2.1.47.1.1.1";
        leaf entPhysicalIndex {
          type PhysicalIndex;
          tailf:snmp-oid "1.3.6.1.2.1.47.1.1.1.1.1";
        }
        leaf entPhysicalDescr {
          type SNMP-FRAMEWORK-MIB:SnmpAdminString;
          tailf:snmp-oid "1.3.6.1.2.1.47.1.1.1.1.2";
          config false;
        }
        leaf entPhysicalVendorType {
          type SNMPv2-TC:AutonomousType;
          tailf:snmp-oid "1.3.6.1.2.1.47.1.1.1.1.3";
          config false;
        }
        leaf entPhysicalContainedIn {
          type entPhysicalContainedInType;
          tailf:snmp-oid "1.3.6.1.2.1.47.1.1.1.1.4";
          config false;
        }
        leaf entPhysicalClass {
          type PhysicalClass;
          tailf:snmp-oid "1.3.6.1.2.1.47.1.1.1.1.5";
          config false;
        }
        leaf entPhysicalParentRelPos {
          type entPhysicalParentRelPosType;
          tailf:snmp-oid "1.3.6.1.2.1.47.1.1.1.1.6";
          config false;
        }
        leaf entPhysicalName {
          type SNMP-FRAMEWORK-MIB:SnmpAdminString;
          tailf:snmp-oid "1.3.6.1.2.1.47.1.1.1.1.7";
          config false;
        }
        leaf entPhysicalHardwareRev {
          type SNMP-FRAMEWORK-MIB:SnmpAdminString;
          tailf:snmp-oid "1.3.6.1.2.1.47.1.1.1.1.8";
          config false;
        }
        leaf entPhysicalFirmwareRev {
          type SNMP-FRAMEWORK-MIB:SnmpAdminString;
          tailf:snmp-oid "1.3.6.1.2.1.47.1.1.1.1.9";
          config false;
        }
        leaf entPhysicalSoftwareRev {
          type SNMP-FRAMEWORK-MIB:SnmpAdminString;
          tailf:snmp-oid "1.3.6.1.2.1.47.1.1.1.1.10";
          config false;
        }
        leaf entPhysicalSerialNum {
          type entPhysicalSerialNumType;
          tailf:snmp-oid "1.3.6.1.2.1.47.1.1.1.1.11";
          config false;
        }
        leaf entPhysicalMfgName {
          type SNMP-FRAMEWORK-MIB:SnmpAdminString;
          tailf:snmp-oid "1.3.6.1.2.1.47.1.1.1.1.12";
          config false;
        }
        leaf entPhysicalModelName {
          type SNMP-FRAMEWORK-MIB:SnmpAdminString;
          tailf:snmp-oid "1.3.6.1.2.1.47.1.1.1.1.13";
          config false;
        }
        leaf entPhysicalAlias {
          type entPhysicalAliasType;
          tailf:snmp-oid "1.3.6.1.2.1.47.1.1.1.1.14";
          config false;
        }
        leaf entPhysicalAssetID {
          type entPhysicalAssetIDType;
          tailf:snmp-oid "1.3.6.1.2.1.47.1.1.1.1.15";
          config false;
        }
        leaf entPhysicalIsFRU {
          type SNMPv2-TC:TruthValue;
          tailf:snmp-oid "1.3.6.1.2.1.47.1.1.1.1.16";
          config false;
        }
      }
    }
    container entLogicalTable {
      config false;
      list entLogicalEntry {
        key "entLogicalIndex";
        tailf:sort-order "snmp";
        config false;
        tailf:snmp-oid "1.3.6.1.2.1.47.1.2.1";
        leaf entLogicalIndex {
          type entLogicalIndexType;
          tailf:snmp-oid "1.3.6.1.2.1.47.1.2.1.1.1";
        }
        leaf entLogicalDescr {
          type SNMP-FRAMEWORK-MIB:SnmpAdminString;
          tailf:snmp-oid "1.3.6.1.2.1.47.1.2.1.1.2";
          config false;
        }
        leaf entLogicalType {
          type SNMPv2-TC:AutonomousType;
          tailf:snmp-oid "1.3.6.1.2.1.47.1.2.1.1.3";
          config false;
        }
        leaf entLogicalCommunity {
          type entLogicalCommunityType;
          tailf:snmp-oid "1.3.6.1.2.1.47.1.2.1.1.4";
          config false;
        }
        leaf entLogicalTAddress {
          type SNMPv2-TC:TAddress;
          tailf:snmp-oid "1.3.6.1.2.1.47.1.2.1.1.5";
          config false;
        }
        leaf entLogicalTDomain {
          type SNMPv2-TC:TDomain;
          tailf:snmp-oid "1.3.6.1.2.1.47.1.2.1.1.6";
          config false;
        }
        leaf entLogicalContextEngineID {
          type SnmpEngineIdOrNone;
          tailf:snmp-oid "1.3.6.1.2.1.47.1.2.1.1.7";
          config false;
        }
        leaf entLogicalContextName {
          type SNMP-FRAMEWORK-MIB:SnmpAdminString;
          tailf:snmp-oid "1.3.6.1.2.1.47.1.2.1.1.8";
          config false;
        }
      }
    }
    container entLPMappingTable {
      config false;
      list entLPMappingEntry {
        key "entLogicalIndex entLPPhysicalIndex";
        tailf:sort-order "snmp";
        config false;
        tailf:snmp-oid "1.3.6.1.2.1.47.1.3.1";
        leaf entLogicalIndex {
          type entLogicalIndexType;
          tailf:snmp-oid "1.3.6.1.2.1.47.1.2.1.1.1";
        }
        leaf entLPPhysicalIndex {
          type PhysicalIndex;
          tailf:snmp-oid "1.3.6.1.2.1.47.1.3.1.1.1";
        }
      }
    }
    container entAliasMappingTable {
      config false;
      list entAliasMappingEntry {
        key "entPhysicalIndex entAliasLogicalIndexOrZero";
        tailf:sort-order "snmp";
        config false;
        tailf:snmp-oid "1.3.6.1.2.1.47.1.3.2";
        leaf entPhysicalIndex {
          type PhysicalIndex;
          tailf:snmp-oid "1.3.6.1.2.1.47.1.1.1.1.1";
        }
        leaf entAliasLogicalIndexOrZero {
          type entAliasLogicalIndexOrZeroType;
          tailf:snmp-oid "1.3.6.1.2.1.47.1.3.2.1.1";
        }
        leaf entAliasMappingIdentifier {
          type SNMPv2-TC:RowPointer;
          tailf:snmp-oid "1.3.6.1.2.1.47.1.3.2.1.2";
          config false;
        }
      }
    }
    container entPhysicalContainsTable {
      config false;
      list entPhysicalContainsEntry {
        key "entPhysicalIndex entPhysicalChildIndex";
        tailf:sort-order "snmp";
        config false;
        tailf:snmp-oid "1.3.6.1.2.1.47.1.3.3";
        leaf entPhysicalIndex {
          type PhysicalIndex;
          tailf:snmp-oid "1.3.6.1.2.1.47.1.1.1.1.1";
        }
        leaf entPhysicalChildIndex {
          type PhysicalIndex;
          tailf:snmp-oid "1.3.6.1.2.1.47.1.3.3.1.1";
        }
      }
    }
  }

  typedef PhysicalIndex {
    type int32 {
      range "1 .. 2147483647";
    }
  }

  typedef PhysicalClass {
    type enumeration {
      enum "other" {
        value 1;
      }
      enum "unknown" {
        value 2;
      }
      enum "chassis" {
        value 3;
      }
      enum "backplane" {
        value 4;
      }
      enum "container" {
        value 5;
      }
      enum "powerSupply" {
        value 6;
      }
      enum "fan" {
        value 7;
      }
      enum "sensor" {
        value 8;
      }
      enum "module" {
        value 9;
      }
      enum "port" {
        value 10;
      }
      enum "stack" {
        value 11;
      }
    }
  }

  typedef SnmpEngineIdOrNone {
    type tailf:hex-list {
      tailf:value-length "min .. 32";
    }
  }

  typedef entPhysicalContainedInType {
    type int32 {
      range "0 .. 2147483647";
    }
  }

  typedef entPhysicalParentRelPosType {
    type int32 {
      range "-1 .. 2147483647";
    }
  }

  typedef entPhysicalSerialNumType {
    type string {
      length "min .. 32";
    }
  }

  typedef entPhysicalAliasType {
    type string {
      length "min .. 32";
    }
  }

  typedef entPhysicalAssetIDType {
    type string {
      length "min .. 32";
    }
  }

  typedef entLogicalIndexType {
    type int32 {
      range "1 .. 2147483647";
    }
  }

  typedef entLogicalCommunityType {
    type tailf:hex-list {
      tailf:value-length "min .. 255";
    }
  }

  typedef entAliasLogicalIndexOrZeroType {
    type int32 {
      range "0 .. 2147483647";
    }
  }
}
