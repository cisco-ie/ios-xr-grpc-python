module aaa_show {
  namespace "http://www.cisco.com/calvados/aaa_show";
  prefix aaa_show;
  import tailf-aaa {
    prefix aaa;
  }
  organization "Cisco Systems Inc.";
  contact
    "clos-mgbl@cisco.com";

  description 
    "This module contains definitions
     for the Calvados model objects.

    This module defines yang model
for logging user/date who accessed
shell last time

    Copyright (c) 2012-2016 by Cisco Systems, Inc.
     All rights reserved.";
  revision 2011-06-20 {
    description
      "Initial revision";
  }

  augment "/aaa:aaa" {
    container privileged-access {
      config false;
      leaf shell-access {
        type string;
        mandatory false;
      }
      leaf first-user {
        type string;
        mandatory false;
      }
      leaf first-user-change {
        type string;
        mandatory false;
      }
      leaf current-disaster-recovery-user {
        type string;
        mandatory false;
      }
    }
    container accounting {
      config false;
      leaf log-data {
        type string;
        mandatory false;
      }
    }
    container user-group {
      config false;
      leaf grp-data {
        type string;
        mandatory false;
      }
    }
  }
}
