module fpd {
  namespace "http://cisco.com/calvados/fpd";
  prefix fpd;

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    FPD CLI support for both oper and config

    Copyright (c) 2012-2016 by Cisco Systems, Inc.
     All rights reserved.";
  revision 2011-12-03 {
    description
      "Initial revision.";
  }

  container fpd {
    uses fpd;
  }

  grouping fpd {
    container config {
      description
        "fpd config mode";
      uses global-fpd-config-group;
    }
  }

  grouping global-fpd-config-group {
    leaf auto-upgrade {
      config true;
      type enumeration {
        enum "enable";
        enum "disable";
      }
      default "disable";
    }
  }
}
