module wd_diskmon {
  namespace "http://cisco.com/calvados/wd_diskmon";
  prefix wd_diskmon;

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2016 by Cisco Systems, Inc.
     All rights reserved.";

  revision "2015-08-30" {
    description "Initial version.";
  }


  typedef percent {
    type int32 {
      range "0 .. 100";
    }
    description
      "Percentage";
  }
  container disk_status_config {
    leaf minor {
      type percent;
      default "80";
      description
        "Disk  Monitoring Minor Threshold";
    }
    leaf severe {
      type percent;
      default "90";
      description
        "Disk Monitoring  Severe Threshold";
    }
    leaf critical {
      type percent;
      default "95";
      description
        "Disk Monitoring Critial  Threshold";
    }
    must " (critical > severe and  severe >  minor)" {
      error-message " minor < severe < critical error ";
    }
  }
  container disk_status {
    description
      "Disk Info";
    config false;
    list all-locations {
      key "location";
      leaf location {
        type string;
      }
      list all-disks {
        key "disk";
        leaf disk {
          type string;
          description
            "Disk name";
        }
        leaf minor {
          type string;
          description
            "Disk  Monitoring Minor Threshold";
        }
        leaf severe {
          type string;
          description
            "Disk Monitoring  Severe Threshold";
        }
        leaf critical {
          type string;
          description
            "Disk Monitoring Critial  Threshold";
        }
        leaf current_state {
          type string;
          description
            " Current state of Disk ";
        }
      }
    }
  }
}
